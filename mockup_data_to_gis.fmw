FME workspace mockup_data_to_gis.fmw

Parameters:
- SourceDataset_XLSXR = G:\Jaetut Drivet\Liiketoiminta\Helsingin kaupunki\KUVA_Palveluverkkosuunnittelun toimintamalli ja tietopohja\Projekti\Vaihe 2\Suunnittelu ja työskentely\Palveluverkkosuunnitelma PowerBI Mockup\mockup_data.xlsx   # Source Microsoft Excel File(s)
- SourceDataset_WFS = https://kartta.hel.fi/ws/geoserver/avoindata/wfs   # Source WFS (Web Feature Service) URL
- DestDataset_GEOJSON = C:\temp\hki_kuva_pvs\hki_kuva_pcs\palvelupaikat_kartalla.json   # Destination GeoJSON File
- PASSED_TEST_GROUP_OUTPUT = ALL   # First Passing Port,FIRST%All Passing Ports,ALL Test Output
- SourceDataset_WFS_9 = https://kartta.hel.fi/ws/geoserver/avoindata/wfs   # Source WFS (Web Feature Service) URL
- SourceDataset_WFS_7 = https://kartta.hel.fi/ws/geoserver/avoindata/wfs   # Source WFS (Web Feature Service) URL
- SourceDataset_WFS_6 = https://lipas.fi/geoserver/lipas/ows   # Source WFS (Web Feature Service) URL
- SourceDataset_WFS_8 = https://lipas.fi/geoserver/lipas/ows   # Source WFS (Web Feature Service) URL
- DestDataset_GEOJSON_3 = C:\temp\hki_kuva_pvs\hki_kuva_pvs\palvelupaikat_kartalla.json   # Destination GeoJSON File
- DestDataset_CSV2_5 = C:\temp\hki_kuva_pvs\hki_kuva_pvs   # Destination CSV (Comma Separated Value) Folder
- DestDataset_CSV2_6 = C:\temp\hki_kuva_pvs\hki_kuva_pvs   # Destination CSV (Comma Separated Value) Folder
- DestDataset_CSV2_7 = C:\temp\hki_kuva_pvs\kuva_pvs_demo   # Destination CSV (Comma Separated Value) Folder
- DestDataset_CSV2 = C:\temp\hki_kuva_pvs\hki_kuva_pvs   # Destination CSV (Comma Separated Value) Folder

Readers:
- XLSXR_1: XLSXR from $(SourceDataset_XLSXR)
- WFS_2: WFS from $(SourceDataset_WFS) in EPSG:3879
- WFS_1: WFS from $(SourceDataset_WFS_9) in EPSG:3879
- WFS_3: WFS from $(SourceDataset_WFS_7) in EPSG:3879
- WFS_4: WFS from $(SourceDataset_WFS_6) in EPSG:3067
- WFS_5: WFS from $(SourceDataset_WFS_8) in EPSG:3067

Writers:
- GEOJSON_1: GEOJSON to $(DestDataset_GEOJSON)
- GEOJSON_2: GEOJSON to $(DestDataset_GEOJSON_3)
- CSV2_1: CSV2 to $(DestDataset_CSV2)
- CSV2_2: CSV2 to $(DestDataset_CSV2_5)
- CSV2_4: CSV2 to $(DestDataset_CSV2_6)
- CSV2_3: CSV2 to $(DestDataset_CSV2_7)

TestFilter_2
    DEFAULT_VALUE = <UNFILTERED>
    PASSED_TEST_GROUP_OUTPUT = FIRST
    TEST_LIST = "BOOL_OP,OR,COMPOSITE_TEST,""""""1"""""",TEST_CLAUSE,TEST @Value(id) = 55ed20a5-6a3a-447c-958c-2b537b9e6ee2",KUVA
    KUVA -> AttributeManager_2
    KUVA -> AttributeRemover_2
TestFilter
    DEFAULT_VALUE = <UNFILTERED>
    PASSED_TEST_GROUP_OUTPUT = $(PASSED_TEST_GROUP_OUTPUT)
    TEST_LIST = "BOOL_OP,OR,COMPOSITE_TEST,""""""1"""""",TEST_CLAUSE,TEST @Value(parent_id) = 55ed20a5-6a3a-447c-958c-2b537b9e6ee2",KUVA as parent id,"BOOL_OP,OR,COMPOSITE_TEST,""""""1"""""",TEST_CLAUSE,TEST @Value(parent_id) = 8bdb8e14-b243-4a1d-b162-ad7b778c3e66",liikunta as parent id,"BOOL_OP,OR,COMPOSITE_TEST,""""""1"""""",TEST_CLAUSE,TEST @Value(parent_id) = ee79f073-1c5a-4228-9021-8f6b2d0feeab",kulttuuri as parent id,"BOOL_OP,OR,COMPOSITE_TEST,""""""1"""""",TEST_CLAUSE,TEST @Value(parent_id) = cfe4d81b-7366-4ae2-b87b-b986e10cd220",nuoriso as parent id,"BOOL_OP,OR,COMPOSITE_TEST,""""""1"""""",TEST_CLAUSE,TEST @Value(parent_id) = 318ba6ff-38cf-4d40-bd4c-4b5bc060cd11",kuva hallinto- ja tukipalvelut as parent id,"BOOL_OP,OR,COMPOSITE_TEST,""""""1"""""",TEST_CLAUSE,TEST @Value(parent_id) = 33f727d3-8788-4121-9e5e-77f133a41018",kirjasto
    KUVA as parent id -> FeatureJoiner_4 [LEFT]
    liikunta as parent id -> FeatureJoiner_5 [LEFT]
    kulttuuri as parent id -> FeatureJoiner_5 [LEFT]
    nuoriso as parent id -> FeatureJoiner_5 [LEFT]
    kuva hallinto- ja tukipalvelut as parent id -> FeatureJoiner_5 [LEFT]
    <UNFILTERED> -> FeatureJoiner [LEFT]
    kirjasto -> FeatureJoiner_5 [LEFT]
AttributeRemover_2
    -> AttributeManager
AttributeManager
    ATTR_TABLE:
      REMOVE _creation_instance (uint64)
      REMOVE _response_body (buffer)
      REMOVE _http_status_code (buffer)
      REMOVE json_type (buffer)
      REMOVE json_index (uint32)
    -> FeatureJoiner_3 [RIGHT]
Toimipisterekisteri_yksikot (reader WFS_2)
    attributes: gml_parent_id xml_buffer, gml_parent_property xml_buffer, gml_id xml_buffer, id xml_int32, org_id xml_buffer, org_id.xsi_nil xml_boolean, dept_id xml_buffer, dept_id.xsi_nil xml_boolean, provider_type xml_buffer, provider_type.xsi_nil xml_boolean, data_source_url xml_buffer, data_source_url.xsi_nil xml_boolean, name_fi xml_buffer, name_fi.xsi_nil xml_boolean, name_sv xml_buffer, name_sv.xsi_nil xml_boolean, name_en xml_buffer, name_en.xsi_nil xml_boolean, manual_coordinates xml_buffer, manual_coordinates.xsi_nil xml_boolean, street_address_fi xml_buffer, street_address_fi.xsi_nil xml_boolean, street_address_sv xml_buffer, street_address_sv.xsi_nil xml_boolean, street_address_en xml_buffer, street_address_en.xsi_nil xml_boolean, address_zip xml_buffer, address_zip.xsi_nil xml_boolean, address_city_fi xml_buffer, address_city_fi.xsi_nil xml_boolean,
      address_city_sv xml_buffer, address_city_sv.xsi_nil xml_boolean, address_city_en xml_buffer, address_city_en.xsi_nil xml_boolean, phone xml_buffer, phone.xsi_nil xml_boolean, call_charge_info_fi xml_buffer, call_charge_info_fi.xsi_nil xml_boolean, call_charge_info_sv xml_buffer, call_charge_info_sv.xsi_nil xml_boolean, call_charge_info_en xml_buffer, call_charge_info_en.xsi_nil xml_boolean, email xml_buffer, email.xsi_nil xml_boolean, www_fi xml_buffer, www_fi.xsi_nil xml_boolean, www_sv xml_buffer, www_sv.xsi_nil xml_boolean, www_en xml_buffer, www_en.xsi_nil xml_boolean, address_postal_full_fi xml_buffer, address_postal_full_fi.xsi_nil xml_boolean, address_postal_full_sv xml_buffer, address_postal_full_sv.xsi_nil xml_boolean, address_postal_full_en xml_buffer, address_postal_full_en.xsi_nil xml_boolean, streetview_entrance_url xml_buffer, streetview_entrance_url.xsi_nil xml_boolean, extra_searchwords_fi xml_buffer, extra_searchwords_fi.xsi_nil xml_boolean,
      accessibility_phone xml_buffer, accessibility_phone.xsi_nil xml_boolean, accessibility_email xml_buffer, accessibility_email.xsi_nil xml_boolean, accessibility_viewpoints xml_buffer, accessibility_viewpoints.xsi_nil xml_boolean, created_time xml_date, created_time.xsi_nil xml_boolean, modified_time xml_date, modified_time.xsi_nil xml_boolean, service_ids xml_buffer, service_ids.xsi_nil xml_boolean, service_fi xml_buffer, service_fi.xsi_nil xml_boolean, service_sv xml_buffer, service_sv.xsi_nil xml_boolean, service_en xml_buffer, service_en.xsi_nil xml_boolean, vtj_prt xml_buffer, vtj_prt.xsi_nil xml_boolean, vtj_prt_verified xml_buffer, vtj_prt_verified.xsi_nil xml_boolean, datanomistaja xml_buffer, datanomistaja.xsi_nil xml_boolean, paivitetty_tietopalveluun xml_date, paivitetty_tietopalveluun.xsi_nil xml_boolean, geom xml_geometry
    -> AttributeRemover
AttributeRemover
    REMOVE_ATTRS = accessibility_email,accessibility_email.xsi_nil,accessibility_phone,accessibility_phone.xsi_nil,accessibility_viewpoints,accessibility_viewpoints.xsi_nil,address_city_en,address_city_en.xsi_nil,address_city_fi,address_city_fi.xsi_nil,address_city_sv,address_city_sv.xsi_nil,address_postal_full_en,address_postal_full_en.xsi_nil,address_postal_full_fi,address_postal_full_fi.xsi_nil,address_postal_full_sv,address_postal_full_sv.xsi_nil,address_zip,address_zip.xsi_nil,call_charge_info_en,call_charge_info_en.xsi_nil,call_charge_info_fi,call_charge_info_fi.xsi_nil,call_charge_info_sv,call_charge_info_sv.xsi_nil,created_time,created_time.xsi_nil,data_source_url,data_source_url.xsi_nil,datanomistaja,datanomistaja.xsi_nil,dept_id.xsi_nil,email,email.xsi_nil,extra_searchwords_fi,extra_searchwords_fi.xsi_nil,geom,gml_id,gml_parent_id,gml_parent_property,manual_coordinates,manual_coordinates.xsi_nil,modified_time,modified_time.xsi_nil,name_en,name_en.xsi_nil,name_fi.xsi_nil,name_sv,name_sv.xsi_nil,org_id.xsi_nil,paivitetty_tietopalveluun.xsi_nil,phone,phone.xsi_nil,provider_type.xsi_nil,service_en,service_en.xsi_nil,service_fi,service_fi.xsi_nil,service_ids,service_ids.xsi_nil,service_sv,service_sv.xsi_nil,street_address_en,street_address_en.xsi_nil,street_address_fi,street_address_fi.xsi_nil,street_address_sv,street_address_sv.xsi_nil,streetview_entrance_url,streetview_entrance_url.xsi_nil,vtj_prt.xsi_nil,vtj_prt_verified.xsi_nil,www_en,www_en.xsi_nil,www_fi,www_fi.xsi_nil,www_sv,www_sv.xsi_nil
    -> FeatureMerger_2 [SUPPLIER]
    -> FeatureMerger [SUPPLIER]
    -> FeatureJoiner_3 [LEFT]
FeatureJoiner_3
    ATTR_CONFLICT_RES = Prefer Left
    GEOMETRY_HANDLING = Prefer Left
    JOIN_KEYS = dept_id id AUTO
    JOIN_MODE = Inner
    JOINED -> SpatialRelator [Supplier]
    JOINED -> FeatureJoiner_6 [RIGHT]
    JOINED -> SpatialFilter [Candidate]
    UNJOINED_RIGHT -> SpatialFilter [Candidate]
Palvelupaikat (reader XLSXR_1)
    attributes: Palvelupaikka ID number(2,0), Palvelupaikan lähtötieto ID (TPR ID tai oma paikkatietoaineisto alueilla) char(5), Palvelupaikan lähtötietojärjestelmä char(47), Palvelupaikka (nimi) char(116), PVS luokitus char(15), Tietomallin koodiston mukainen palvelupaikkatyyppi char(11), Palveluverkon suunnittelualue string, Palvelupaikan ryhmitys (KUVA:n tarve) char(44), Lähtötietojärjestelmän lisätieto char(83), Lisäksi paikkatietogeometria / sijaintitieto string
    -> FeatureMerger_2 [REQUESTOR]
FeatureMerger_2
    ATTR_ACCUM_MODE = Merge Supplier
    ATTR_CONFLICT_RES = Use Requestor
    IGNORE_NULLS = No
    JOIN_KEYS = @Value(Palvelupaikka (nimi)) @Value(name_fi) AUTO
    MERGE_TYPE = Attributes and Geometry
    PROCESS_DUPS = NO
    REJECT_NULL_MISSING_KEYS = No
    SUPPLIERS_FIRST = No
    MERGED -> Reprojector
    UNMERGED_REQUESTOR -> FeatureMerger [REQUESTOR]
FeatureMerger
    ATTR_ACCUM_MODE = Merge Supplier
    ATTR_CONFLICT_RES = Use Requestor
    IGNORE_NULLS = No
    JOIN_KEYS = @Value(Palvelupaikan lähtötieto ID (TPR ID tai oma paikkatietoaineisto alueilla)) @Value(id) AUTO
    MERGE_TYPE = Attributes Only
    PROCESS_DUPS = NO
    REJECT_NULL_MISSING_KEYS = No
    SUPPLIERS_FIRST = No
    MERGED -> Reprojector
Reprojector
    DEST = EPSG:4326
    INTERPOLATION_TYPE_NAME = Nearest Neighbor
    RASTER_CELL_SIZE = Preserve Cells
    RASTER_TOLERANCE = 0.0
    SOURCE = EPSG:3879
    REPROJECTED -> palvelupaikat (writer GEOJSON_1)
palvelupaikat (writer GEOJSON_1)
    attributes: Palvelupaikka ID int, Palvelupaikan lähtötieto ID (TPR ID tai oma paikkatietoaineisto alueilla) string, Palvelupaikan lähtötietojärjestelmä string, Palvelupaikka (nimi) string, PVS luokitus string, Tietomallin koodiston mukainen palvelupaikkatyyppi string, Palveluverkon suunnittelualue string, Palvelupaikan ryhmitys (KUVA:n tarve) string, Lähtötietojärjestelmän lisätieto string, Lisäksi paikkatietogeometria / sijaintitieto string, id int, org_id string, dept_id string, provider_type string, name_fi string, vtj_prt string, vtj_prt_verified string, paivitetty_tietopalveluun string
Rakennukset_piste_rekisteritiedot (reader WFS_1)
    attributes: gml_parent_id xml_buffer, gml_parent_property xml_buffer, gml_id xml_buffer, id xml_int32, kg_krakenn xml_int32, kg_krakenn.xsi_nil xml_boolean, i_pyraknro xml_int32, i_pyraknro.xsi_nil xml_boolean, c_vtj_prt xml_buffer, c_vtj_prt.xsi_nil xml_boolean, c_kiinteistotunnus xml_buffer, c_kiinteistotunnus.xsi_nil xml_boolean, i_nkoord xml_int32, i_nkoord.xsi_nil xml_boolean, i_ekoord xml_int32, i_ekoord.xsi_nil xml_boolean, c_valmpvm xml_datetime, c_valmpvm.xsi_nil xml_boolean, c_julkisivu xml_buffer, c_julkisivu.xsi_nil xml_boolean, i_kokala xml_real64, i_kokala.xsi_nil xml_boolean, i_kerrlkm xml_real64, i_kerrlkm.xsi_nil xml_boolean, i_kerrosala xml_real64, i_kerrosala.xsi_nil xml_boolean, i_kellarala xml_real64, i_kellarala.xsi_nil xml_boolean, d_ashuoala xml_real64, d_ashuoala.xsi_nil xml_boolean,
      c_kayttark xml_buffer, c_kayttark.xsi_nil xml_boolean, c_lammtapa xml_buffer, c_lammtapa.xsi_nil xml_boolean, c_poltaine xml_buffer, c_poltaine.xsi_nil xml_boolean, c_rakeaine xml_buffer, c_rakeaine.xsi_nil xml_boolean, i_raktilav xml_real64, i_raktilav.xsi_nil xml_boolean, c_hissi xml_buffer, c_hissi.xsi_nil xml_boolean, c_viemlii xml_buffer, c_viemlii.xsi_nil xml_boolean, c_vesilii xml_buffer, c_vesilii.xsi_nil xml_boolean, c_sahkolii xml_buffer, c_sahkolii.xsi_nil xml_boolean, i_huoneistojen_lkm xml_real64, i_huoneistojen_lkm.xsi_nil xml_boolean, katunimi_suomi xml_buffer, katunimi_suomi.xsi_nil xml_boolean, katunimi_ruotsi xml_buffer, katunimi_ruotsi.xsi_nil xml_boolean, osoitenumero xml_buffer, osoitenumero.xsi_nil xml_boolean, postinumero xml_buffer, postinumero.xsi_nil xml_boolean, datanomistaja xml_buffer, datanomistaja.xsi_nil xml_boolean,
      paivitetty_tietopalveluun xml_date, paivitetty_tietopalveluun.xsi_nil xml_boolean, geom xml_geometry, c_rakennusluokka xml_buffer, c_rakennusluokka.xsi_nil xml_boolean, i_asuinhuoneistojen_lkm xml_int32, i_asuinhuoneistojen_lkm.xsi_nil xml_boolean, i_toimitilojen_lkm xml_int32, i_toimitilojen_lkm.xsi_nil xml_boolean
    -> AttributeRemover_3
AttributeRemover_3
    REMOVE_ATTRS = c_hissi,c_hissi.xsi_nil,c_julkisivu,c_julkisivu.xsi_nil,c_kayttark.xsi_nil,c_kiinteistotunnus.xsi_nil,c_lammtapa,c_lammtapa.xsi_nil,c_poltaine,c_poltaine.xsi_nil,c_rakeaine,c_rakeaine.xsi_nil,c_rakennusluokka.xsi_nil,c_sahkolii,c_sahkolii.xsi_nil,c_valmpvm.xsi_nil,c_vesilii,c_vesilii.xsi_nil,c_viemlii,c_viemlii.xsi_nil,c_vtj_prt.xsi_nil,d_ashuoala,d_ashuoala.xsi_nil,datanomistaja,datanomistaja.xsi_nil,geom,gml_id,gml_parent_id,gml_parent_property,i_asuinhuoneistojen_lkm,i_asuinhuoneistojen_lkm.xsi_nil,i_ekoord,i_ekoord.xsi_nil,i_huoneistojen_lkm,i_huoneistojen_lkm.xsi_nil,i_kellarala,i_kellarala.xsi_nil,i_kerrlkm,i_kerrlkm.xsi_nil,i_kerrosala.xsi_nil,i_kokala,i_kokala.xsi_nil,i_nkoord,i_nkoord.xsi_nil,i_pyraknro,i_pyraknro.xsi_nil,i_raktilav,i_raktilav.xsi_nil,i_toimitilojen_lkm,i_toimitilojen_lkm.xsi_nil,katunimi_ruotsi,katunimi_ruotsi.xsi_nil,katunimi_suomi,katunimi_suomi.xsi_nil,kg_krakenn,kg_krakenn.xsi_nil,osoitenumero,osoitenumero.xsi_nil,paivitetty_tietopalveluun,paivitetty_tietopalveluun.xsi_nil,postinumero,postinumero.xsi_nil
    -> FeatureJoiner_6 [LEFT]
FeatureJoiner_6
    ATTR_CONFLICT_RES = Prefer Left
    GEOMETRY_HANDLING = Prefer Left
    JOIN_KEYS = c_vtj_prt vtj_prt AUTO
    JOIN_MODE = Inner
    JOINED -> FeatureJoiner_6_Joined
    UNJOINED_RIGHT -> FeatureJoiner_6_UnjoinedRight
FeatureJoiner_6_Joined: Inspector
FeatureJoiner_6_UnjoinedRight: Inspector
Rakennukset_alue_rekisteritiedot (reader WFS_3)
    attributes: gml_parent_id xml_buffer, gml_parent_property xml_buffer, gml_id xml_buffer, id xml_int32, id.xsi_nil xml_boolean, kuntarekisteri_id xml_int32, kuntarekisteri_id.xsi_nil xml_boolean, kg_krakenn xml_int32, kg_krakenn.xsi_nil xml_boolean, ratu xml_real64, ratu.xsi_nil xml_boolean, vtj_prt xml_buffer, vtj_prt.xsi_nil xml_boolean, tyyppi xml_buffer, tyyppi.xsi_nil xml_boolean, tyyppi_koodi xml_real64, tyyppi_koodi.xsi_nil xml_boolean, tila xml_buffer, tila.xsi_nil xml_boolean, tila_koodi xml_real64, tila_koodi.xsi_nil xml_boolean, ratu_vastaavuus xml_buffer, ratu_vastaavuus.xsi_nil xml_boolean, ratu_vastaavuus_koodi xml_real64, ratu_vastaavuus_koodi.xsi_nil xml_boolean, ratu_laatu xml_buffer, ratu_laatu.xsi_nil xml_boolean, ratu_laatu_koodi xml_real64, ratu_laatu_koodi.xsi_nil xml_boolean, i_raktilav xml_real64,
      i_raktilav.xsi_nil xml_boolean, i_pyraknro xml_int32, i_pyraknro.xsi_nil xml_boolean, i_nkoord xml_int32, i_nkoord.xsi_nil xml_boolean, i_ekoord xml_int32, i_ekoord.xsi_nil xml_boolean, i_kokala xml_real64, i_kokala.xsi_nil xml_boolean, i_kerrosala xml_real64, i_kerrosala.xsi_nil xml_boolean, i_kerrlkm xml_real64, i_kerrlkm.xsi_nil xml_boolean, i_kellarala xml_real64, i_kellarala.xsi_nil xml_boolean, i_huoneistojen_lkm xml_real64, i_huoneistojen_lkm.xsi_nil xml_boolean, d_ashuoala xml_real64, d_ashuoala.xsi_nil xml_boolean, c_vtj_prt xml_buffer, c_vtj_prt.xsi_nil xml_boolean, c_viemlii xml_buffer, c_viemlii.xsi_nil xml_boolean, c_vesilii xml_buffer, c_vesilii.xsi_nil xml_boolean, c_valmpvm xml_datetime, c_valmpvm.xsi_nil xml_boolean, c_sahkolii xml_buffer, c_sahkolii.xsi_nil xml_boolean, c_rakeaine xml_buffer,
      c_rakeaine.xsi_nil xml_boolean, c_poltaine xml_buffer, c_poltaine.xsi_nil xml_boolean, c_lammtapa xml_buffer, c_lammtapa.xsi_nil xml_boolean, c_kiinteistotunnus xml_buffer, c_kiinteistotunnus.xsi_nil xml_boolean, c_kayttark xml_buffer, c_kayttark.xsi_nil xml_boolean, c_julkisivu xml_buffer, c_julkisivu.xsi_nil xml_boolean, c_hissi xml_buffer, c_hissi.xsi_nil xml_boolean, katunimi_suomi xml_buffer, katunimi_suomi.xsi_nil xml_boolean, katunimi_ruotsi xml_buffer, katunimi_ruotsi.xsi_nil xml_boolean, osoitenumero xml_buffer, osoitenumero.xsi_nil xml_boolean, postinumero xml_buffer, postinumero.xsi_nil xml_boolean, muokkauspvm xml_date, muokkauspvm.xsi_nil xml_boolean, luontipvm xml_date, luontipvm.xsi_nil xml_boolean, datanomistaja xml_buffer, datanomistaja.xsi_nil xml_boolean, paivitetty_tietopalveluun xml_date, paivitetty_tietopalveluun.xsi_nil xml_boolean, geom xml_geometry,
      tietopalvelu_id xml_int32, c_rakennusluokka xml_buffer, c_rakennusluokka.xsi_nil xml_boolean, i_asuinhuoneistojen_lkm xml_int32, i_asuinhuoneistojen_lkm.xsi_nil xml_boolean, i_toimitilojen_lkm xml_int32, i_toimitilojen_lkm.xsi_nil xml_boolean
    -> AttributeRemover_4
AttributeRemover_4
    REMOVE_ATTRS = c_hissi,c_hissi.xsi_nil,c_julkisivu,c_julkisivu.xsi_nil,c_kayttark.xsi_nil,c_kiinteistotunnus.xsi_nil,c_lammtapa,c_lammtapa.xsi_nil,c_poltaine,c_poltaine.xsi_nil,c_rakeaine,c_rakeaine.xsi_nil,c_rakennusluokka.xsi_nil,c_sahkolii,c_sahkolii.xsi_nil,c_valmpvm.xsi_nil,c_vesilii,c_vesilii.xsi_nil,c_viemlii,c_viemlii.xsi_nil,c_vtj_prt.xsi_nil,d_ashuoala,d_ashuoala.xsi_nil,datanomistaja,datanomistaja.xsi_nil,geom,gml_id,gml_parent_id,gml_parent_property,i_asuinhuoneistojen_lkm,i_asuinhuoneistojen_lkm.xsi_nil,i_ekoord,i_ekoord.xsi_nil,i_huoneistojen_lkm,i_huoneistojen_lkm.xsi_nil,i_kellarala,i_kellarala.xsi_nil,i_kerrlkm,i_kerrlkm.xsi_nil,i_kerrosala.xsi_nil,i_kokala,i_kokala.xsi_nil,i_nkoord,i_nkoord.xsi_nil,i_pyraknro,i_pyraknro.xsi_nil,i_raktilav,i_raktilav.xsi_nil,i_toimitilojen_lkm,i_toimitilojen_lkm.xsi_nil,katunimi_ruotsi,katunimi_ruotsi.xsi_nil,katunimi_suomi,katunimi_suomi.xsi_nil,kg_krakenn,kg_krakenn.xsi_nil,osoitenumero,osoitenumero.xsi_nil,paivitetty_tietopalveluun,paivitetty_tietopalveluun.xsi_nil,postinumero,postinumero.xsi_nil,id.xsi_nil,kuntarekisteri_id.xsi_nil,luontipvm,luontipvm.xsi_nil,muokkauspvm,muokkauspvm.xsi_nil,ratu,ratu.xsi_nil,ratu_laatu,ratu_laatu.xsi_nil,ratu_laatu_koodi,ratu_laatu_koodi.xsi_nil,ratu_vastaavuus,ratu_vastaavuus.xsi_nil,ratu_vastaavuus_koodi,ratu_vastaavuus_koodi.xsi_nil,tietopalvelu_id,tila.xsi_nil,tyyppi.xsi_nil,tyyppi_koodi.xsi_nil,vtj_prt.xsi_nil
    -> SpatialRelator [Requestor]
SpatialRelator
    AGGREGATE_HANDLING = Yes
    CALC_CARD = No
    CURVE_BOUNDARY_RULE_PARAM = Default Rule
    PREDICATES = CONTAINS
    SUCCESS_ATTR = _related_suppliers
    -> TestFilter_3
TestFilter_3
    DEFAULT_VALUE = <UNFILTERED>
    PASSED_TEST_GROUP_OUTPUT = FIRST
    TEST_LIST = "BOOL_OP,OR,COMPOSITE_TEST,""""""1"""""",TEST_CLAUSE,TEST @Value(_related_suppliers) > 0",ok
    ok -> AttributeManager_16
AttributeManager_16
    ATTR_TABLE = SET_TO palvelupaikka (buffer) = rakennus
    USER_EXPOSED_ATTRIBUTES = palvelupaikka
    -> CenterPointReplacer
    -> SpatialFilter [Filter]
CenterPointReplacer
    POINTTYPE = CENTEROFGRAV
    POINT -> Counter
    POINT -> FeatureMerger_3 [REQUESTOR]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> FeatureMerger_7 [REQUESTOR]
    FAILED -> AttributeManager_6
AttributeManager_6
    ATTR_TABLE = SET_TO palvelupaikka (buffer) = tuntematon
    -> Counter
    -> FeatureMerger_4 [REQUESTOR]
lipas_kaikki_reitit (reader WFS_4)
    attributes: gml_parent_id xml_buffer, gml_parent_property xml_buffer, gml_id xml_buffer, id xml_int32, id.xsi_nil xml_boolean, tyyppikoodi xml_int32, tyyppikoodi.xsi_nil xml_boolean, tyyppikoodi_alaryhma xml_buffer, tyyppikoodi_alaryhma.xsi_nil xml_boolean, tyyppikoodi_paaryhma xml_buffer, tyyppikoodi_paaryhma.xsi_nil xml_boolean, sijainti_id xml_int32, sijainti_id.xsi_nil xml_boolean, reitisto_id xml_int32, reitisto_id.xsi_nil xml_boolean, katuosoite xml_buffer, katuosoite.xsi_nil xml_boolean, postinumero xml_buffer, postinumero.xsi_nil xml_boolean, postitoimipaikka xml_buffer, postitoimipaikka.xsi_nil xml_boolean, kuntanumero xml_int32, kuntanumero.xsi_nil xml_boolean, kunta_nimi_fi xml_buffer, kunta_nimi_fi.xsi_nil xml_boolean, lisatieto_fi xml_buffer, lisatieto_fi.xsi_nil xml_boolean, reitti_id xml_int32, reitti_id.xsi_nil xml_boolean, tyyppi_nimi_fi xml_buffer,
      tyyppi_nimi_fi.xsi_nil xml_boolean, tyyppi_nimi_se xml_buffer, tyyppi_nimi_se.xsi_nil xml_boolean, tyyppi_nimi_en xml_buffer, tyyppi_nimi_en.xsi_nil xml_boolean, nimi_fi xml_buffer, nimi_fi.xsi_nil xml_boolean, nimi_se xml_buffer, nimi_se.xsi_nil xml_boolean, www xml_buffer, www.xsi_nil xml_boolean, sahkoposti xml_buffer, sahkoposti.xsi_nil xml_boolean, puhelinnumero xml_buffer, puhelinnumero.xsi_nil xml_boolean, omistaja xml_buffer, omistaja.xsi_nil xml_boolean, yllapitaja xml_buffer, yllapitaja.xsi_nil xml_boolean, reitti_nimi_fi xml_buffer, reitti_nimi_fi.xsi_nil xml_boolean, reitti_nimi_se xml_buffer, reitti_nimi_se.xsi_nil xml_boolean, reittiosa_json xml_buffer, reittiosa_json.xsi_nil xml_boolean, the_geom xml_geometry, x xml_real64, x.xsi_nil xml_boolean, y xml_real64, y.xsi_nil xml_boolean
    -> TestFilter_4
TestFilter_4
    DEFAULT_VALUE = <UNFILTERED>
    PASSED_TEST_GROUP_OUTPUT = FIRST
    TEST_LIST = "BOOL_OP,OR,COMPOSITE_TEST,""""""1"""""",TEST_CLAUSE,TEST @Value(kunta_nimi_fi) = Helsinki",Helsinki
    Helsinki -> Reprojector_2
Reprojector_2
    DEST = EPSG:3879
    INTERPOLATION_TYPE_NAME = Nearest Neighbor
    RASTER_CELL_SIZE = Preserve Cells
    RASTER_TOLERANCE = 0.0
    REPROJECTED -> AttributeManager_8
AttributeManager_8
    ATTR_TABLE = SET_TO palvelupaikka (buffer) = ulkotila (reitti)
    -> Counter
    -> FeatureMerger_5 [REQUESTOR]
lipas_kaikki_alueet (reader WFS_5)
    attributes: gml_parent_id xml_buffer, gml_parent_property xml_buffer, gml_id xml_buffer, id xml_int32, id.xsi_nil xml_boolean, tyyppikoodi xml_int32, tyyppikoodi.xsi_nil xml_boolean, tyyppikoodi_alaryhma xml_buffer, tyyppikoodi_alaryhma.xsi_nil xml_boolean, tyyppikoodi_paaryhma xml_buffer, tyyppikoodi_paaryhma.xsi_nil xml_boolean, sijainti_id xml_int32, sijainti_id.xsi_nil xml_boolean, alue_id xml_int32, alue_id.xsi_nil xml_boolean, katuosoite xml_buffer, katuosoite.xsi_nil xml_boolean, postinumero xml_buffer, postinumero.xsi_nil xml_boolean, postitoimipaikka xml_buffer, postitoimipaikka.xsi_nil xml_boolean, kuntanumero xml_int32, kuntanumero.xsi_nil xml_boolean, kunta_nimi_fi xml_buffer, kunta_nimi_fi.xsi_nil xml_boolean, tyyppi_nimi_fi xml_buffer, tyyppi_nimi_fi.xsi_nil xml_boolean, tyyppi_nimi_se xml_buffer, tyyppi_nimi_se.xsi_nil xml_boolean, tyyppi_nimi_en xml_buffer,
      tyyppi_nimi_en.xsi_nil xml_boolean, nimi_fi xml_buffer, nimi_fi.xsi_nil xml_boolean, nimi_se xml_buffer, nimi_se.xsi_nil xml_boolean, www xml_buffer, www.xsi_nil xml_boolean, sahkoposti xml_buffer, sahkoposti.xsi_nil xml_boolean, puhelinnumero xml_buffer, puhelinnumero.xsi_nil xml_boolean, omistaja xml_buffer, omistaja.xsi_nil xml_boolean, yllapitaja xml_buffer, yllapitaja.xsi_nil xml_boolean, lisatieto_fi xml_buffer, lisatieto_fi.xsi_nil xml_boolean, osa_alue_json xml_buffer, osa_alue_json.xsi_nil xml_boolean, the_geom xml_geometry, x xml_real64, x.xsi_nil xml_boolean, y xml_real64, y.xsi_nil xml_boolean
    -> TestFilter_5
TestFilter_5
    DEFAULT_VALUE = <UNFILTERED>
    PASSED_TEST_GROUP_OUTPUT = FIRST
    TEST_LIST = "BOOL_OP,OR,COMPOSITE_TEST,""""""1"""""",TEST_CLAUSE,TEST @Value(kunta_nimi_fi) = Helsinki",Helsinki
    Helsinki -> AttributeManager_10
AttributeManager_10
    ATTR_TABLE = SET_TO palvelupaikka (buffer) = ulkotila (reitti)
    -> AttributeManager_9
AttributeManager_9
    ATTR_TABLE:
      SET_TO palvelupaikka (buffer) = ulkotila (reitti)
      SET_TO palvelupaikka (buffer) = ulkotila (alue)
    -> Counter
    -> FeatureMerger_6 [REQUESTOR]
Counter
    CNT_ATTR = counter
    DOMAIN = counter
    SCOPE = Global
    START = 1
    -> AttributeRemover_5
    -> FeatureMerger_3 [SUPPLIER]
    -> FeatureMerger_4 [SUPPLIER]
    -> FeatureMerger_5 [SUPPLIER]
    -> FeatureMerger_6 [SUPPLIER]
    -> FeatureMerger_7 [SUPPLIER]
FeatureMerger_3
    ATTR_ACCUM_MODE = Merge Supplier
    ATTR_CONFLICT_RES = Use Requestor
    IGNORE_NULLS = No
    JOIN_KEYS = @Value(c_vtj_prt) @Value(c_vtj_prt) AUTO
    MERGE_TYPE = Attributes Only
    PROCESS_DUPS = NO
    REJECT_NULL_MISSING_KEYS = No
    SUPPLIERS_FIRST = No
    MERGED -> AttributeManager_11
AttributeManager_11
    ATTR_TABLE:
      REMOVE id (int32)
      REMOVE kuntarekisteri_id (int32)
      REMOVE tyyppi_koodi (real64)
      REMOVE tila_koodi (real64)
      REMOVE tila_koodi.xsi_nil (logical)
      REMOVE _related_suppliers (uint32)
      SET_TO palvelupaikka (buffer) = rakennus
      REMOVE org_id (buffer)
      REMOVE dept_id (buffer)
      REMOVE provider_type (buffer)
      REMOVE name_fi (buffer)
      REMOVE vtj_prt_verified (buffer)
      REMOVE paivitetty_tietopalveluun (buffer)
      REMOVE oid (buffer)
      REMOVE hierarchy_level (buffer)
      REMOVE business_id (buffer)
      REMOVE parent_id (buffer)
      REMOVE organization_type (buffer)
      REMOVE municipality_code (buffer)
      REMOVE parent_id_level4 (buffer)
      REMOVE parent_name_fi_level4 (buffer)
      REMOVE parent_id_level3 (buffer)
      REMOVE parent_name_fi_level3 (buffer)
      REMOVE parent_id_level2 (buffer)
      REMOVE parent_name_fi_level2 (buffer)
      REMOVE parent_id_level1 (buffer)
      REMOVE parent_name_fi_level1 (buffer)
      REMOVE palvelupaikka (buffer)
      REMOVE gml_parent_id (buffer)
      REMOVE gml_parent_property (buffer)
      REMOVE gml_id (buffer)
      REMOVE id.xsi_nil (logical)
      REMOVE tyyppikoodi (int32)
      REMOVE tyyppikoodi.xsi_nil (logical)
      REMOVE tyyppikoodi_alaryhma (buffer)
      REMOVE tyyppikoodi_alaryhma.xsi_nil (logical)
      REMOVE tyyppikoodi_paaryhma (buffer)
      REMOVE tyyppikoodi_paaryhma.xsi_nil (logical)
      REMOVE sijainti_id (int32)
      REMOVE sijainti_id.xsi_nil (logical)
      REMOVE reitisto_id (int32)
      REMOVE reitisto_id.xsi_nil (logical)
      REMOVE katuosoite (buffer)
      REMOVE katuosoite.xsi_nil (logical)
      REMOVE postinumero (buffer)
      REMOVE postinumero.xsi_nil (logical)
      REMOVE postitoimipaikka (buffer)
      REMOVE postitoimipaikka.xsi_nil (logical)
      REMOVE kuntanumero (int32)
      REMOVE kuntanumero.xsi_nil (logical)
      REMOVE kunta_nimi_fi (buffer)
      REMOVE kunta_nimi_fi.xsi_nil (logical)
      REMOVE lisatieto_fi (buffer)
      REMOVE lisatieto_fi.xsi_nil (logical)
      REMOVE reitti_id (int32)
      REMOVE reitti_id.xsi_nil (logical)
      REMOVE tyyppi_nimi_fi (buffer)
      REMOVE tyyppi_nimi_fi.xsi_nil (logical)
      REMOVE tyyppi_nimi_se (buffer)
      REMOVE tyyppi_nimi_se.xsi_nil (logical)
      REMOVE tyyppi_nimi_en (buffer)
      REMOVE tyyppi_nimi_en.xsi_nil (logical)
      REMOVE nimi_fi (buffer)
      REMOVE nimi_fi.xsi_nil (logical)
      REMOVE nimi_se (buffer)
      REMOVE nimi_se.xsi_nil (logical)
      REMOVE www (buffer)
      REMOVE www.xsi_nil (logical)
      REMOVE sahkoposti (buffer)
      REMOVE sahkoposti.xsi_nil (logical)
      REMOVE puhelinnumero (buffer)
      REMOVE puhelinnumero.xsi_nil (logical)
      REMOVE omistaja (buffer)
      REMOVE omistaja.xsi_nil (logical)
      REMOVE yllapitaja (buffer)
      REMOVE yllapitaja.xsi_nil (logical)
      REMOVE reitti_nimi_fi (buffer)
      REMOVE reitti_nimi_fi.xsi_nil (logical)
      REMOVE reitti_nimi_se (buffer)
      REMOVE reitti_nimi_se.xsi_nil (logical)
      REMOVE reittiosa_json (buffer)
      REMOVE reittiosa_json.xsi_nil (logical)
      REMOVE the_geom (buffer)
      REMOVE x (real64)
      REMOVE x.xsi_nil (logical)
      REMOVE y (real64)
      REMOVE y.xsi_nil (logical)
      REMOVE alue_id (int32)
      REMOVE alue_id.xsi_nil (logical)
      REMOVE osa_alue_json (buffer)
      REMOVE osa_alue_json.xsi_nil (logical)
    USER_EXPOSED_ATTRIBUTES = palvelupaikka
    -> rakennusten_ominaisuustiedot (writer CSV2_1)
rakennusten_ominaisuustiedot (writer CSV2_1)
    attributes: vtj_prt string, tyyppi string, tila string, i_kerrosala string, c_vtj_prt string, c_valmpvm string, c_kiinteistotunnus string, c_kayttark string, c_rakennusluokka string, counter int64
FeatureMerger_7
    ATTR_ACCUM_MODE = Merge Supplier
    ATTR_CONFLICT_RES = Use Requestor
    IGNORE_NULLS = No
    JOIN_KEYS = @Value(id) @Value(id) AUTO
    MERGE_TYPE = Attributes Only
    PROCESS_DUPS = NO
    REJECT_NULL_MISSING_KEYS = No
    SUPPLIERS_FIRST = No
    UNMERGED_REQUESTOR -> AttributeManager_14
AttributeManager_14
    ATTR_TABLE:
      REMOVE paivitetty_tietopalveluun (buffer)
      REMOVE kuntarekisteri_id (int32)
      REMOVE tyyppi (buffer)
      REMOVE tyyppi_koodi (real64)
      REMOVE tila (buffer)
      REMOVE tila_koodi (real64)
      REMOVE tila_koodi.xsi_nil (logical)
      REMOVE i_kerrosala (real64)
      REMOVE c_vtj_prt (buffer)
      REMOVE c_valmpvm (buffer)
      REMOVE c_kiinteistotunnus (buffer)
      REMOVE c_kayttark (buffer)
      REMOVE c_rakennusluokka (buffer)
      REMOVE _related_suppliers (uint32)
      REMOVE _predicate (buffer)
    -> palvelupaikat (writer CSV2_2)
AttributeRemover_5
    REMOVE_ATTRS = _related_suppliers,alue_id,alue_id.xsi_nil,business_id,c_kayttark,c_kiinteistotunnus,c_rakennusluokka,c_valmpvm,c_vtj_prt,dept_id,gml_id,gml_parent_id,gml_parent_property,hierarchy_level,i_kerrosala,id,id.xsi_nil,katuosoite,katuosoite.xsi_nil,kunta_nimi_fi,kunta_nimi_fi.xsi_nil,kuntanumero,kuntanumero.xsi_nil,kuntarekisteri_id,lisatieto_fi,lisatieto_fi.xsi_nil,municipality_code,name_fi,nimi_fi,nimi_fi.xsi_nil,nimi_se,nimi_se.xsi_nil,oid,omistaja,omistaja.xsi_nil,org_id,organization_type,osa_alue_json,osa_alue_json.xsi_nil,paivitetty_tietopalveluun,parent_id,parent_id_level1,parent_id_level2,parent_id_level3,parent_id_level4,parent_name_fi_level1,parent_name_fi_level2,parent_name_fi_level3,parent_name_fi_level4,postinumero,postinumero.xsi_nil,postitoimipaikka,postitoimipaikka.xsi_nil,provider_type,puhelinnumero,puhelinnumero.xsi_nil,reitisto_id,reitisto_id.xsi_nil,reitti_id,reitti_id.xsi_nil,reitti_nimi_fi,reitti_nimi_fi.xsi_nil,reitti_nimi_se,reitti_nimi_se.xsi_nil,reittiosa_json,reittiosa_json.xsi_nil,sahkoposti,sahkoposti.xsi_nil,sijainti_id,sijainti_id.xsi_nil,the_geom,tila,tila_koodi,tila_koodi.xsi_nil,tyyppi,tyyppi_koodi,tyyppi_nimi_en,tyyppi_nimi_en.xsi_nil,tyyppi_nimi_fi,tyyppi_nimi_fi.xsi_nil,tyyppi_nimi_se,tyyppi_nimi_se.xsi_nil,tyyppikoodi,tyyppikoodi.xsi_nil,tyyppikoodi_alaryhma,tyyppikoodi_alaryhma.xsi_nil,tyyppikoodi_paaryhma,tyyppikoodi_paaryhma.xsi_nil,vtj_prt,vtj_prt_verified,www,www.xsi_nil,x,x.xsi_nil,y,y.xsi_nil,yllapitaja,yllapitaja.xsi_nil
    -> palvelupaikat_geojson (writer GEOJSON_2)
    -> palvelupaikat_unique (writer CSV2_3)
palvelupaikat_geojson (writer GEOJSON_2)
    attributes: palvelupaikka string, counter int
palvelupaikat_unique (writer CSV2_3)
    attributes: palvelupaikka string, counter int64
FeatureMerger_4
    ATTR_ACCUM_MODE = Merge Supplier
    ATTR_CONFLICT_RES = Use Requestor
    IGNORE_NULLS = No
    JOIN_KEYS = @Value(id) @Value(id) AUTO
    MERGE_TYPE = Attributes Only
    PROCESS_DUPS = NO
    REJECT_NULL_MISSING_KEYS = No
    SUPPLIERS_FIRST = No
    MERGED -> AttributeManager_7
AttributeManager_7
    ATTR_TABLE:
      REMOVE paivitetty_tietopalveluun (buffer)
      REMOVE gml_parent_id (buffer)
      REMOVE gml_parent_property (buffer)
      REMOVE gml_id (buffer)
      REMOVE id.xsi_nil (logical)
      REMOVE tyyppikoodi (int32)
      REMOVE tyyppikoodi.xsi_nil (logical)
      REMOVE tyyppikoodi_alaryhma (buffer)
      REMOVE tyyppikoodi_alaryhma.xsi_nil (logical)
      REMOVE tyyppikoodi_paaryhma (buffer)
      REMOVE tyyppikoodi_paaryhma.xsi_nil (logical)
      REMOVE sijainti_id (int32)
      REMOVE sijainti_id.xsi_nil (logical)
      REMOVE reitisto_id (int32)
      REMOVE reitisto_id.xsi_nil (logical)
      REMOVE katuosoite (buffer)
      REMOVE katuosoite.xsi_nil (logical)
      REMOVE postinumero (buffer)
      REMOVE postinumero.xsi_nil (logical)
      REMOVE postitoimipaikka (buffer)
      REMOVE postitoimipaikka.xsi_nil (logical)
      REMOVE kuntanumero (int32)
      REMOVE kuntanumero.xsi_nil (logical)
      REMOVE kunta_nimi_fi (buffer)
      REMOVE kunta_nimi_fi.xsi_nil (logical)
      REMOVE lisatieto_fi (buffer)
      REMOVE lisatieto_fi.xsi_nil (logical)
      REMOVE reitti_id (int32)
      REMOVE reitti_id.xsi_nil (logical)
      REMOVE tyyppi_nimi_fi (buffer)
      REMOVE tyyppi_nimi_fi.xsi_nil (logical)
      REMOVE tyyppi_nimi_se (buffer)
      REMOVE tyyppi_nimi_se.xsi_nil (logical)
      REMOVE tyyppi_nimi_en (buffer)
      REMOVE tyyppi_nimi_en.xsi_nil (logical)
      REMOVE nimi_fi (buffer)
      REMOVE nimi_fi.xsi_nil (logical)
      REMOVE nimi_se (buffer)
      REMOVE nimi_se.xsi_nil (logical)
      REMOVE www (buffer)
      REMOVE www.xsi_nil (logical)
      REMOVE sahkoposti (buffer)
      REMOVE sahkoposti.xsi_nil (logical)
      REMOVE puhelinnumero (buffer)
      REMOVE puhelinnumero.xsi_nil (logical)
      REMOVE omistaja (buffer)
      REMOVE omistaja.xsi_nil (logical)
      REMOVE yllapitaja (buffer)
      REMOVE yllapitaja.xsi_nil (logical)
      REMOVE reitti_nimi_fi (buffer)
      REMOVE reitti_nimi_fi.xsi_nil (logical)
      REMOVE reitti_nimi_se (buffer)
      REMOVE reitti_nimi_se.xsi_nil (logical)
      REMOVE reittiosa_json (buffer)
      REMOVE reittiosa_json.xsi_nil (logical)
      REMOVE the_geom (buffer)
      REMOVE x (real64)
      REMOVE x.xsi_nil (logical)
      REMOVE y (real64)
      REMOVE y.xsi_nil (logical)
      REMOVE alue_id (int32)
      REMOVE alue_id.xsi_nil (logical)
      REMOVE osa_alue_json (buffer)
      REMOVE osa_alue_json.xsi_nil (logical)
      REMOVE kuntarekisteri_id (int32)
      REMOVE tyyppi (buffer)
      REMOVE tyyppi_koodi (real64)
      REMOVE tila (buffer)
      REMOVE tila_koodi (real64)
      REMOVE tila_koodi.xsi_nil (logical)
      REMOVE i_kerrosala (real64)
      REMOVE c_vtj_prt (buffer)
      REMOVE c_valmpvm (buffer)
      REMOVE c_kiinteistotunnus (buffer)
      REMOVE c_kayttark (buffer)
      REMOVE c_rakennusluokka (buffer)
      REMOVE _related_suppliers (uint32)
    -> palvelupaikat (writer CSV2_2)
FeatureMerger_5
    ATTR_ACCUM_MODE = Merge Supplier
    ATTR_CONFLICT_RES = Use Requestor
    IGNORE_NULLS = No
    JOIN_KEYS = @Value(id) @Value(id) AUTO
    MERGE_TYPE = Attributes Only
    PROCESS_DUPS = NO
    REJECT_NULL_MISSING_KEYS = No
    SUPPLIERS_FIRST = No
    MERGED -> AttributeManager_12
    MERGED -> AttributeManager_13
FeatureMerger_6
    ATTR_ACCUM_MODE = Merge Supplier
    ATTR_CONFLICT_RES = Use Requestor
    IGNORE_NULLS = No
    JOIN_KEYS = @Value(id) @Value(id) AUTO
    MERGE_TYPE = Attributes Only
    PROCESS_DUPS = NO
    REJECT_NULL_MISSING_KEYS = No
    SUPPLIERS_FIRST = No
    MERGED -> AttributeManager_12
    MERGED -> AttributeManager_13
AttributeManager_13
    ATTR_TABLE:
      REMOVE gml_parent_id (buffer)
      REMOVE gml_parent_property (buffer)
      REMOVE gml_id (buffer)
      REMOVE id.xsi_nil (logical)
      REMOVE tyyppikoodi (int32)
      REMOVE tyyppikoodi.xsi_nil (logical)
      REMOVE tyyppikoodi_alaryhma (buffer)
      REMOVE tyyppikoodi_alaryhma.xsi_nil (logical)
      REMOVE tyyppikoodi_paaryhma (buffer)
      REMOVE tyyppikoodi_paaryhma.xsi_nil (logical)
      REMOVE sijainti_id (int32)
      REMOVE sijainti_id.xsi_nil (logical)
      REMOVE katuosoite (buffer)
      REMOVE katuosoite.xsi_nil (logical)
      REMOVE postinumero (buffer)
      REMOVE postinumero.xsi_nil (logical)
      REMOVE postitoimipaikka (buffer)
      REMOVE postitoimipaikka.xsi_nil (logical)
      REMOVE kuntanumero (int32)
      REMOVE kuntanumero.xsi_nil (logical)
      REMOVE kunta_nimi_fi (buffer)
      REMOVE kunta_nimi_fi.xsi_nil (logical)
      REMOVE lisatieto_fi (buffer)
      REMOVE lisatieto_fi.xsi_nil (logical)
      REMOVE tyyppi_nimi_fi (buffer)
      REMOVE tyyppi_nimi_fi.xsi_nil (logical)
      REMOVE tyyppi_nimi_se (buffer)
      REMOVE tyyppi_nimi_se.xsi_nil (logical)
      REMOVE tyyppi_nimi_en (buffer)
      REMOVE tyyppi_nimi_en.xsi_nil (logical)
      RENAME_SET_VALUE nimi_fi > name_fi (buffer)
      REMOVE nimi_fi.xsi_nil (logical)
      REMOVE nimi_se (buffer)
      REMOVE nimi_se.xsi_nil (logical)
      REMOVE www (buffer)
      REMOVE www.xsi_nil (logical)
      REMOVE sahkoposti (buffer)
      REMOVE sahkoposti.xsi_nil (logical)
      REMOVE puhelinnumero (buffer)
      REMOVE puhelinnumero.xsi_nil (logical)
      REMOVE omistaja (buffer)
      REMOVE omistaja.xsi_nil (logical)
      REMOVE yllapitaja (buffer)
      REMOVE yllapitaja.xsi_nil (logical)
      REMOVE the_geom (buffer)
      REMOVE x (real64)
      REMOVE x.xsi_nil (logical)
      REMOVE y (real64)
      REMOVE y.xsi_nil (logical)
      REMOVE alue_id (int32)
      REMOVE alue_id.xsi_nil (logical)
      REMOVE osa_alue_json (buffer)
      REMOVE osa_alue_json.xsi_nil (logical)
      REMOVE name_fi (buffer)
      REMOVE paivitetty_tietopalveluun (buffer)
      SET_TO parent_name_fi_level2 (buffer) = Liikunta
      SET_TO parent_name_fi_level1 (buffer) = Kulttuurin ja vapaa-ajan toimiala
      REMOVE reitisto_id (int32)
      REMOVE reitisto_id.xsi_nil (logical)
      REMOVE reitti_id (int32)
      REMOVE reitti_id.xsi_nil (logical)
      REMOVE reitti_nimi_fi (buffer)
      REMOVE reitti_nimi_fi.xsi_nil (logical)
      REMOVE reitti_nimi_se (buffer)
      REMOVE reitti_nimi_se.xsi_nil (logical)
      REMOVE reittiosa_json (buffer)
      REMOVE reittiosa_json.xsi_nil (logical)
      REMOVE kuntarekisteri_id (int32)
      REMOVE tyyppi (buffer)
      REMOVE tyyppi_koodi (real64)
      REMOVE tila (buffer)
      REMOVE tila_koodi (real64)
      REMOVE tila_koodi.xsi_nil (logical)
      REMOVE i_kerrosala (real64)
      REMOVE c_vtj_prt (buffer)
      REMOVE c_valmpvm (buffer)
      REMOVE c_kiinteistotunnus (buffer)
      REMOVE c_kayttark (buffer)
      REMOVE c_rakennusluokka (buffer)
      REMOVE _related_suppliers (uint32)
    -> palvelupaikat (writer CSV2_2)
palvelupaikat (writer CSV2_2)
    attributes: id string, org_id string, dept_id string, provider_type string, name_fi string, vtj_prt string, vtj_prt_verified string, oid string, hierarchy_level string, business_id string, parent_id string, organization_type string, municipality_code string, parent_id_level4 string, parent_name_fi_level4 string, parent_id_level3 string, parent_name_fi_level3 string, parent_id_level2 string, parent_name_fi_level2 string, parent_id_level1 string, parent_name_fi_level1 string, palvelupaikka string, counter int64
AttributeManager_12
    ATTR_TABLE:
      REMOVE gml_parent_id (buffer)
      REMOVE gml_parent_property (buffer)
      REMOVE gml_id (buffer)
      REMOVE id.xsi_nil (logical)
      REMOVE tyyppikoodi.xsi_nil (logical)
      REMOVE tyyppikoodi_alaryhma.xsi_nil (logical)
      REMOVE tyyppikoodi_paaryhma.xsi_nil (logical)
      REMOVE sijainti_id.xsi_nil (logical)
      REMOVE reitisto_id.xsi_nil (logical)
      REMOVE katuosoite (buffer)
      REMOVE katuosoite.xsi_nil (logical)
      REMOVE postinumero (buffer)
      REMOVE postinumero.xsi_nil (logical)
      REMOVE postitoimipaikka (buffer)
      REMOVE postitoimipaikka.xsi_nil (logical)
      REMOVE kuntanumero (int32)
      REMOVE kuntanumero.xsi_nil (logical)
      REMOVE kunta_nimi_fi.xsi_nil (logical)
      REMOVE lisatieto_fi.xsi_nil (logical)
      REMOVE reitti_id.xsi_nil (logical)
      REMOVE tyyppi_nimi_fi.xsi_nil (logical)
      REMOVE tyyppi_nimi_se (buffer)
      REMOVE tyyppi_nimi_se.xsi_nil (logical)
      REMOVE tyyppi_nimi_en (buffer)
      REMOVE tyyppi_nimi_en.xsi_nil (logical)
      REMOVE nimi_fi.xsi_nil (logical)
      REMOVE nimi_se (buffer)
      REMOVE nimi_se.xsi_nil (logical)
      REMOVE www (buffer)
      REMOVE www.xsi_nil (logical)
      REMOVE sahkoposti (buffer)
      REMOVE sahkoposti.xsi_nil (logical)
      REMOVE puhelinnumero (buffer)
      REMOVE puhelinnumero.xsi_nil (logical)
      REMOVE omistaja.xsi_nil (logical)
      REMOVE yllapitaja.xsi_nil (logical)
      REMOVE reitti_nimi_fi.xsi_nil (logical)
      REMOVE reitti_nimi_se (buffer)
      REMOVE reitti_nimi_se.xsi_nil (logical)
      REMOVE reittiosa_json (buffer)
      REMOVE reittiosa_json.xsi_nil (logical)
      REMOVE the_geom (buffer)
      REMOVE x (real64)
      REMOVE x.xsi_nil (logical)
      REMOVE y (real64)
      REMOVE y.xsi_nil (logical)
      REMOVE org_id (buffer)
      REMOVE dept_id (buffer)
      REMOVE provider_type (buffer)
      REMOVE name_fi (buffer)
      REMOVE vtj_prt (buffer)
      REMOVE vtj_prt_verified (buffer)
      REMOVE paivitetty_tietopalveluun (buffer)
      REMOVE oid (buffer)
      REMOVE hierarchy_level (buffer)
      REMOVE business_id (buffer)
      REMOVE parent_id (buffer)
      REMOVE organization_type (buffer)
      REMOVE municipality_code (buffer)
      REMOVE parent_id_level4 (buffer)
      REMOVE parent_name_fi_level4 (buffer)
      REMOVE parent_id_level3 (buffer)
      REMOVE parent_name_fi_level3 (buffer)
      REMOVE parent_id_level2 (buffer)
      REMOVE parent_name_fi_level2 (buffer)
      REMOVE parent_id_level1 (buffer)
      REMOVE parent_name_fi_level1 (buffer)
      REMOVE alue_id (int32)
      REMOVE alue_id.xsi_nil (logical)
      REMOVE osa_alue_json (buffer)
      REMOVE osa_alue_json.xsi_nil (logical)
      REMOVE kuntarekisteri_id (int32)
      REMOVE tyyppi (buffer)
      REMOVE tyyppi_koodi (real64)
      REMOVE tila (buffer)
      REMOVE tila_koodi (real64)
      REMOVE tila_koodi.xsi_nil (logical)
      REMOVE i_kerrosala (real64)
      REMOVE c_vtj_prt (buffer)
      REMOVE c_valmpvm (buffer)
      REMOVE c_kiinteistotunnus (buffer)
      REMOVE c_kayttark (buffer)
      REMOVE c_rakennusluokka (buffer)
      REMOVE _related_suppliers (uint32)
    -> liikuntapaikkojen_ominaisuustiedot (writer CSV2_4)
liikuntapaikkojen_ominaisuustiedot (writer CSV2_4)
    attributes: id string, tyyppikoodi string, tyyppikoodi_alaryhma string, tyyppikoodi_paaryhma string, sijainti_id string, reitisto_id string, kunta_nimi_fi string, lisatieto_fi string, reitti_id string, tyyppi_nimi_fi string, nimi_fi string, omistaja string, yllapitaja string, reitti_nimi_fi string, palvelupaikka string, counter int64

Bookmark: HKI Palvelurekisterin departments
Creator_2
    GEOMTYPE = Geometry Object
    NUM = 1
    CREATED -> HTTPCaller_2
HTTPCaller_2
    ADDITIONAL_URL_PARAMETERS = organization;83e74666-0836-4c1d-948a-4b34a8b90301
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://www.hel.fi/palvelukarttaws/rest/v4/department/
    TRANSFER_TIMEOUT_LENGTH = 90
    USE_COOKIES = No
    VERIFY_SSL_CERTIFICATES = Yes
    -> JSONFragmenter_2
JSONFragmenter_2
    EXPLODE_FORMAT = JSON
    EXTRACT_ATTR = Yes
    JSON_ATTR = _response_body
    JSON_QUERY = json[*]
    NEW_ATTRIBUTES = id parent_id org_id hierarchy_level business_id organization_type municipality_code oid name_fi
    READ_FROM_FILE = NO
    RECURSIVE = Yes
    REJECT_EMPTY_LISTS = YES
    FRAGMENTS -> TestFilter
    FRAGMENTS -> TestFilter_2

Bookmark: toimintayksiköt KUVAn eri hierarkiatasoilla
AttributeManager_2
    ATTR_TABLE:
      REMOVE _creation_instance (uint64)
      REMOVE _response_body (buffer)
      REMOVE _http_status_code (buffer)
      REMOVE json_type (buffer)
      REMOVE json_index (uint32)
      RENAME_SET_VALUE id > parent_id_level1 (buffer)
      REMOVE parent_id (buffer)
      REMOVE org_id (buffer)
      REMOVE hierarchy_level (buffer)
      REMOVE business_id (buffer)
      REMOVE organization_type (buffer)
      REMOVE municipality_code (buffer)
      REMOVE oid (buffer)
      RENAME_SET_VALUE name_fi > parent_name_fi_level1 (buffer)
    -> FeatureJoiner_4 [RIGHT]
FeatureJoiner_4
    ATTR_CONFLICT_RES = Prefer Left
    GEOMETRY_HANDLING = Prefer Left
    JOIN_KEYS = parent_id parent_id_level1 AUTO
    JOIN_MODE = Inner
    JOINED -> AttributeManager_5
    JOINED -> AttributeRemover_2
AttributeManager_5
    ATTR_TABLE:
      REMOVE _creation_instance (uint64)
      REMOVE _response_body (buffer)
      REMOVE _http_status_code (buffer)
      REMOVE json_type (buffer)
      REMOVE json_index (uint32)
      RENAME_SET_VALUE id > parent_id_level2 (buffer)
      REMOVE parent_id (buffer)
      REMOVE org_id (buffer)
      REMOVE hierarchy_level (buffer)
      REMOVE business_id (buffer)
      REMOVE organization_type (buffer)
      REMOVE municipality_code (buffer)
      REMOVE oid (buffer)
      RENAME_SET_VALUE name_fi > parent_name_fi_level2 (buffer)
    -> FeatureJoiner_5 [RIGHT]
FeatureJoiner_5
    ATTR_CONFLICT_RES = Prefer Left
    GEOMETRY_HANDLING = Prefer Left
    JOIN_KEYS = parent_id parent_id_level2 AUTO
    JOIN_MODE = Inner
    JOINED -> AttributeManager_3
    JOINED -> AttributeRemover_2
AttributeManager_3
    ATTR_TABLE:
      REMOVE _creation_instance (uint64)
      REMOVE _response_body (buffer)
      REMOVE _http_status_code (buffer)
      REMOVE json_type (buffer)
      REMOVE json_index (uint32)
      RENAME_SET_VALUE id > parent_id_level3 (buffer)
      REMOVE parent_id (buffer)
      REMOVE org_id (buffer)
      REMOVE hierarchy_level (buffer)
      REMOVE business_id (buffer)
      REMOVE organization_type (buffer)
      REMOVE municipality_code (buffer)
      REMOVE oid (buffer)
      RENAME_SET_VALUE name_fi > parent_name_fi_level3 (buffer)
    -> FeatureJoiner [RIGHT]
FeatureJoiner
    ATTR_CONFLICT_RES = Prefer Left
    GEOMETRY_HANDLING = Prefer Left
    JOIN_KEYS = parent_id parent_id_level3 AUTO
    JOIN_MODE = Inner
    JOINED -> AttributeManager_4
    JOINED -> AttributeRemover_2
    UNJOINED_LEFT -> FeatureJoiner_2 [LEFT]
AttributeManager_4
    ATTR_TABLE:
      REMOVE _creation_instance (uint64)
      REMOVE _response_body (buffer)
      REMOVE _http_status_code (buffer)
      REMOVE json_type (buffer)
      REMOVE json_index (uint32)
      RENAME_SET_VALUE id > parent_id_level4 (buffer)
      REMOVE parent_id (buffer)
      REMOVE org_id (buffer)
      REMOVE hierarchy_level (buffer)
      REMOVE business_id (buffer)
      REMOVE organization_type (buffer)
      REMOVE municipality_code (buffer)
      REMOVE oid (buffer)
      RENAME_SET_VALUE name_fi > parent_name_fi_level4 (buffer)
    -> FeatureJoiner_2 [RIGHT]
FeatureJoiner_2
    ATTR_CONFLICT_RES = Prefer Left
    GEOMETRY_HANDLING = Prefer Left
    JOIN_KEYS = parent_id parent_id_level4 AUTO
    JOIN_MODE = Inner
    JOINED -> AttributeRemover_2
